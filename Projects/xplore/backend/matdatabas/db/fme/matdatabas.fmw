FME workspace matdatabas.fmw

Parameters:
- SourceDataset_MSSQL_JDBC_NONSPATIAL = matdatabas 1   # SQL Server Connection
- DestDataset_POSTGRES_6 = matdatabas postgres utv   # Connection

Readers:
- MSSQL_JDBC_NONSPATIAL_1: MSSQL_JDBC_NONSPATIAL from $(SourceDataset_MSSQL_JDBC_NONSPATIAL) in SWEREF-99-TM

Writers:
- POSTGRES_4: POSTGRES to $(DestDataset_POSTGRES_6)

ANVANDARE (reader MSSQL_JDBC_NONSPATIAL_1)
    attributes: ID integer, NAMN nvarchar(130), FORETAG nvarchar(60), AKTIV bit, INLOGGNINGS_NAMN nvarchar(130), BEHORIGHET tinyint, DEFAULT_KARTLAGER_ID integer, SKICKA_EPOST bit, E_POST nvarchar(130), INLOGGAD_SENAST smalldatetime, SKAPAD_DATUM smalldatetime, ANDRAD_DATUM datetime2, ANDRAD_AV_ID integer, AUTHENTICATION_KEY nvarchar(20)
    -> lowercase_3
lowercase_3: BulkAttributeRenamer
    ATTRCHOICE = All Attributes
    CASE_CHANGE_TYPE = lower
    MODE_CHOICE = RENAME
    PATTERN_ACTION_DISP = CASECHANGE
    -> anvandare (writer POSTGRES_4)
anvandare (writer POSTGRES_4)
    attributes: id int4, namn varchar(130), foretag varchar(60), aktiv bool, inloggnings_namn varchar(130), behorighet int2, default_kartlager_id int4, skicka_epost bool, e_post varchar(130), inloggad_senast timestamp, skapad_datum timestamp, andrad_datum timestamp, andrad_av_id int4, authentication_key varchar(20)
ANVANDARGRUPP_ANVANDARE (reader MSSQL_JDBC_NONSPATIAL_1)
    attributes: ANVANDAR_ID integer, ANVANDARGRUPP_ID integer
    -> lowercase_5
lowercase_5: BulkAttributeRenamer
    ATTRCHOICE = All Attributes
    CASE_CHANGE_TYPE = lower
    MODE_CHOICE = RENAME
    PATTERN_ACTION_DISP = CASECHANGE
    -> anvandargrupp_anvandare (writer POSTGRES_4)
anvandargrupp_anvandare (writer POSTGRES_4)
    attributes: anvandar_id int4, anvandargrupp_id int4
MATOBJEKT_BIFOGAT_DOKUMENT (reader MSSQL_JDBC_NONSPATIAL_1)
    attributes: MATOBJEKT_ID integer, BIFOGAD_FIL_ID integer
    -> lowercase_21
lowercase_21: BulkAttributeRenamer
    ATTRCHOICE = All Attributes
    CASE_CHANGE_TYPE = lower
    MODE_CHOICE = RENAME
    PATTERN_ACTION_DISP = CASECHANGE
    -> matobjekt_bifogat_dokument (writer POSTGRES_4)
matobjekt_bifogat_dokument (writer POSTGRES_4)
    attributes: matobjekt_id int4, bifogad_fil_id int4
ANALYS (reader MSSQL_JDBC_NONSPATIAL_1)
    attributes: ID integer, MATOBJEKT_ID integer, ANALYS_DATUM smalldatetime, KOMMENTAR nvarchar(500), RAPPORTOR nvarchar(60)
    -> lowercase
lowercase: BulkAttributeRenamer
    ATTRCHOICE = All Attributes
    CASE_CHANGE_TYPE = lower
    MODE_CHOICE = RENAME
    PATTERN_ACTION_DISP = CASECHANGE
    -> analys (writer POSTGRES_4)
analys (writer POSTGRES_4)
    attributes: id int4, matobjekt_id int4, analys_datum timestamp, kommentar varchar(500), rapportor varchar(60)
ANALYS_BIFOGAD_RAPPORT (reader MSSQL_JDBC_NONSPATIAL_1)
    attributes: ANALYS_ID integer, BIFOGAD_FIL_ID integer
    -> lowercase_2
lowercase_2: BulkAttributeRenamer
    ATTRCHOICE = All Attributes
    CASE_CHANGE_TYPE = lower
    MODE_CHOICE = RENAME
    PATTERN_ACTION_DISP = CASECHANGE
    -> analys_bifogad_rapport (writer POSTGRES_4)
analys_bifogad_rapport (writer POSTGRES_4)
    attributes: analys_id int4, bifogad_fil_id int4
ANVANDARGRUPP (reader MSSQL_JDBC_NONSPATIAL_1)
    attributes: ID integer, NAMN nvarchar(60), BESKRIVNING nvarchar(500), SKAPAD_DATUM smalldatetime, ANDRAD_DATUM datetime2, ANDRAD_AV_ID integer
    -> lowercase_4
lowercase_4: BulkAttributeRenamer
    ATTRCHOICE = All Attributes
    CASE_CHANGE_TYPE = lower
    MODE_CHOICE = RENAME
    PATTERN_ACTION_DISP = CASECHANGE
    -> anvandargrupp (writer POSTGRES_4)
anvandargrupp (writer POSTGRES_4)
    attributes: id int4, namn varchar(60), beskrivning varchar(500), skapad_datum timestamp, andrad_datum timestamp, andrad_av_id int4
BIFOGAD_FIL (reader MSSQL_JDBC_NONSPATIAL_1)
    attributes: ID integer, MIME_TYP nvarchar(130), FILNAMN nvarchar(255), SKAPAD_DATUM smalldatetime, FIL varbinary_max, THUMBNAIL varbinary_max
    -> lowercase_6
lowercase_6: BulkAttributeRenamer
    ATTRCHOICE = All Attributes
    CASE_CHANGE_TYPE = lower
    MODE_CHOICE = RENAME
    PATTERN_ACTION_DISP = CASECHANGE
    -> bifogad_fil (writer POSTGRES_4)
bifogad_fil (writer POSTGRES_4)
    attributes: id int4, mime_typ varchar(130), filnamn varchar(255), skapad_datum timestamp, fil bytea, thumbnail bytea
DEFINITION_MATNINGSTYP (reader MSSQL_JDBC_NONSPATIAL_1)
    attributes: ID integer, MATOBJEKT_TYP tinyint, NAMN nvarchar(60), STORHET nvarchar(20), ENHET nvarchar(12), DECIMALER tinyint, BERAKNAD_STORHET nvarchar(20), BERAKNAD_ENHET nvarchar(12), BERAKNAD_DECIMALER tinyint, FELKODER nvarchar(500), GRAFTYP tinyint, AUTOMATISK_INRAPPORTERING bit, BESKRIVNING nvarchar(500), ANDRINGSBAR bit, SKAPAD_DATUM smalldatetime, ANDRAD_DATUM datetime2, ANDRAD_AV_ID integer
    -> lowercase_7
lowercase_7: BulkAttributeRenamer
    ATTRCHOICE = All Attributes
    CASE_CHANGE_TYPE = lower
    MODE_CHOICE = RENAME
    PATTERN_ACTION_DISP = CASECHANGE
    -> definition_matningstyp (writer POSTGRES_4)
definition_matningstyp (writer POSTGRES_4)
    attributes: id int4, matobjekt_typ int2, namn varchar(60), storhet varchar(20), enhet varchar(12), decimaler int2, beraknad_storhet varchar(20), beraknad_enhet varchar(12), beraknad_decimaler int2, felkoder varchar(500), graftyp int2, automatisk_inrapportering bool, beskrivning varchar(500), andringsbar bool, skapad_datum timestamp, andrad_datum timestamp, andrad_av_id int4
GRANSVARDE (reader MSSQL_JDBC_NONSPATIAL_1)
    attributes: ID integer, MATNINGSTYP_ID integer, TYP_AV_KONTROLL tinyint, GRANSVARDE float, LARMNIVA_ID integer, LARM_TILL_ANVANDARGRUPP_ID integer, SKAPAD_DATUM smalldatetime, ANDRAD_DATUM datetime2, ANDRAD_AV_ID integer
    -> lowercase_8
lowercase_8: BulkAttributeRenamer
    ATTRCHOICE = All Attributes
    CASE_CHANGE_TYPE = lower
    MODE_CHOICE = RENAME
    PATTERN_ACTION_DISP = CASECHANGE
    -> gransvarde (writer POSTGRES_4)
gransvarde (writer POSTGRES_4)
    attributes: id int4, matningstyp_id int4, typ_av_kontroll int2, gransvarde float8, larmniva_id int4, larm_till_anvandargrupp_id int4, skapad_datum timestamp, andrad_datum timestamp, andrad_av_id int4
GRUPP (reader MSSQL_JDBC_NONSPATIAL_1)
    attributes: ID integer, KATEGORI tinyint, NAMN nvarchar(60), KARTSYMBOL tinyint, BESKRIVNING nvarchar(500), SKAPAD_DATUM smalldatetime, ANDRAD_DATUM datetime2, ANDRAD_AV_ID integer
    -> lowercase_9
lowercase_9: BulkAttributeRenamer
    ATTRCHOICE = All Attributes
    CASE_CHANGE_TYPE = lower
    MODE_CHOICE = RENAME
    PATTERN_ACTION_DISP = CASECHANGE
    -> grupp (writer POSTGRES_4)
grupp (writer POSTGRES_4)
    attributes: id int4, kategori int2, namn varchar(60), kartsymbol int2, beskrivning varchar(500), skapad_datum timestamp, andrad_datum timestamp, andrad_av_id int4
GRUPP_MATOBJEKT (reader MSSQL_JDBC_NONSPATIAL_1)
    attributes: MATOBJEKT_ID integer, GRUPP_ID integer
    -> lowercase_10
lowercase_10: BulkAttributeRenamer
    ATTRCHOICE = All Attributes
    CASE_CHANGE_TYPE = lower
    MODE_CHOICE = RENAME
    PATTERN_ACTION_DISP = CASECHANGE
    -> grupp_matobjekt (writer POSTGRES_4)
grupp_matobjekt (writer POSTGRES_4)
    attributes: matobjekt_id int4, grupp_id int4
HANDELSE (reader MSSQL_JDBC_NONSPATIAL_1)
    attributes: ID integer, MATOBJEKT_ID integer, BENAMNING nvarchar(60), BESKRIVNING nvarchar(500), LOGGAD_DATUM smalldatetime, LOGGAD_AV_ID integer
    -> lowercase_11
lowercase_11: BulkAttributeRenamer
    ATTRCHOICE = All Attributes
    CASE_CHANGE_TYPE = lower
    MODE_CHOICE = RENAME
    PATTERN_ACTION_DISP = CASECHANGE
    -> handelse (writer POSTGRES_4)
handelse (writer POSTGRES_4)
    attributes: id int4, matobjekt_id int4, benamning varchar(60), beskrivning varchar(500), loggad_datum timestamp, loggad_av_id int4
HANDELSE_BIFOGAD_BILD (reader MSSQL_JDBC_NONSPATIAL_1)
    attributes: HANDELSE_ID integer, BIFOGAD_FIL_ID integer
    -> lowercase_12
lowercase_12: BulkAttributeRenamer
    ATTRCHOICE = All Attributes
    CASE_CHANGE_TYPE = lower
    MODE_CHOICE = RENAME
    PATTERN_ACTION_DISP = CASECHANGE
    -> handelse_bifogad_bild (writer POSTGRES_4)
handelse_bifogad_bild (writer POSTGRES_4)
    attributes: handelse_id int4, bifogad_fil_id int4
KARTLAGER (reader MSSQL_JDBC_NONSPATIAL_1)
    attributes: ID integer, NAMN nvarchar(60), GRUPP nvarchar(60), ORDNING smallint, VISA bit, BESKRIVNING nvarchar(500), DIREKTLANK bit, OMRADE_N1 numeric(10,3), OMRADE_E1 numeric(10,3), OMRADE_N2 numeric(10,3), OMRADE_E2 numeric(10,3), ANDRINGSBAR bit, SKAPAD_DATUM smalldatetime, ANDRAD_DATUM datetime2, ANDRAD_AV_ID integer
    -> lowercase_13
lowercase_13: BulkAttributeRenamer
    ATTRCHOICE = All Attributes
    CASE_CHANGE_TYPE = lower
    MODE_CHOICE = RENAME
    PATTERN_ACTION_DISP = CASECHANGE
    -> kartlager (writer POSTGRES_4)
kartlager (writer POSTGRES_4)
    attributes: id int4, namn varchar(60), grupp varchar(60), ordning int2, visa bool, beskrivning varchar(500), direktlank bool, omrade_n1 numeric(10,3), omrade_e1 numeric(10,3), omrade_n2 numeric(10,3), omrade_e2 numeric(10,3), andringsbar bool, skapad_datum timestamp, andrad_datum timestamp, andrad_av_id int4
KARTLAGER_FIL (reader MSSQL_JDBC_NONSPATIAL_1)
    attributes: ID integer, KARTLAGER_ID integer, FILNAMN nvarchar(255), SKAPAD_DATUM smalldatetime, FIL nvarchar_max
    -> lowercase_14
lowercase_14: BulkAttributeRenamer
    ATTRCHOICE = All Attributes
    CASE_CHANGE_TYPE = lower
    MODE_CHOICE = RENAME
    PATTERN_ACTION_DISP = CASECHANGE
    -> kartlager_fil (writer POSTGRES_4)
kartlager_fil (writer POSTGRES_4)
    attributes: id int4, kartlager_id int4, filnamn varchar(255), skapad_datum timestamp, fil varchar(80)
LARM (reader MSSQL_JDBC_NONSPATIAL_1)
    attributes: ID bigint, MATOBJEKT_ID integer, GRANSVARDE_ID integer, MATNING_ID bigint, STATUS tinyint
    -> lowercase_15
lowercase_15: BulkAttributeRenamer
    ATTRCHOICE = All Attributes
    CASE_CHANGE_TYPE = lower
    MODE_CHOICE = RENAME
    PATTERN_ACTION_DISP = CASECHANGE
    -> larm (writer POSTGRES_4)
larm (writer POSTGRES_4)
    attributes: id int8, matobjekt_id int4, gransvarde_id int4, matning_id int8, status int2
LARMNIVA (reader MSSQL_JDBC_NONSPATIAL_1)
    attributes: ID integer, NAMN nvarchar(60), BESKRIVNING nvarchar(130), SKAPAD_DATUM smalldatetime, ANDRAD_DATUM datetime2, ANDRAD_AV_ID integer
    -> lowercase_16
lowercase_16: BulkAttributeRenamer
    ATTRCHOICE = All Attributes
    CASE_CHANGE_TYPE = lower
    MODE_CHOICE = RENAME
    PATTERN_ACTION_DISP = CASECHANGE
    -> larmniva (writer POSTGRES_4)
larmniva (writer POSTGRES_4)
    attributes: id int4, namn varchar(60), beskrivning varchar(130), skapad_datum timestamp, andrad_datum timestamp, andrad_av_id int4
MATNING (reader MSSQL_JDBC_NONSPATIAL_1)
    attributes: ID bigint, MATNINGSTYP_ID integer, AVLAST_DATUM smalldatetime, AVLAST_VARDE float, INOM_DETEKTIONSOMRADE tinyint, BERAKNAT_VARDE float, STATUS tinyint, KOMMENTAR nvarchar(250), FELKOD nvarchar(60), RAPPORTOR nvarchar(60)
    -> lowercase_17
lowercase_17: BulkAttributeRenamer
    ATTRCHOICE = All Attributes
    CASE_CHANGE_TYPE = lower
    MODE_CHOICE = RENAME
    PATTERN_ACTION_DISP = CASECHANGE
    -> matning (writer POSTGRES_4)
matning (writer POSTGRES_4)
    attributes: id int8, matningstyp_id int4, avlast_datum timestamp, avlast_varde float8, inom_detektionsomrade int2, beraknat_varde float8, status int2, kommentar varchar(250), felkod varchar(60), rapportor varchar(60)
MATNINGSLOGG (reader MSSQL_JDBC_NONSPATIAL_1)
    attributes: ID bigint, MATNING_ID bigint, LOGGAT_DATUM smalldatetime, LOGGAT_AV_ID integer, HANDELSE tinyint, BESKRIVNING nvarchar(500)
    -> lowercase_18
lowercase_18: BulkAttributeRenamer
    ATTRCHOICE = All Attributes
    CASE_CHANGE_TYPE = lower
    MODE_CHOICE = RENAME
    PATTERN_ACTION_DISP = CASECHANGE
    -> matningslogg (writer POSTGRES_4)
matningslogg (writer POSTGRES_4)
    attributes: id int8, matning_id int8, loggat_datum timestamp, loggat_av_id int4, handelse int2, beskrivning varchar(500)
MATNINGSTYP (reader MSSQL_JDBC_NONSPATIAL_1)
    attributes: ID integer, MATOBJEKT_ID integer, DEFINITION_MATNINGSTYP_ID integer, MATANSVARIG_ANVANDARGRUPP_ID integer, MATINTERVALL_ANTAL_GANGER tinyint, MATINTERVALL_TIDSENHET tinyint, AKTIV bit, PAMINNELSE_DAGAR tinyint, INSTRUMENT nvarchar(60), GRANSKAS_AUTOMATISKT bit, GRANSKAS_MIN float, GRANSKAS_MAX float, BERAKNING_KONSTANT float, BERAKNING_REFERENSNIVA float, MAX_PEJLBART_DJUP float, FIXPUNKT nvarchar(20), ENHET nvarchar(12), DECIMALER tinyint, SKAPAD_DATUM smalldatetime, ANDRAD_DATUM datetime2, ANDRAD_AV_ID integer
    -> lowercase_19
lowercase_19: BulkAttributeRenamer
    ATTRCHOICE = All Attributes
    CASE_CHANGE_TYPE = lower
    MODE_CHOICE = RENAME
    PATTERN_ACTION_DISP = CASECHANGE
    -> matningstyp (writer POSTGRES_4)
matningstyp (writer POSTGRES_4)
    attributes: id int4, matobjekt_id int4, definition_matningstyp_id int4, matansvarig_anvandargrupp_id int4, matintervall_antal_ganger int2, matintervall_tidsenhet int2, aktiv bool, paminnelse_dagar int2, instrument varchar(60), granskas_automatiskt bool, granskas_min float8, granskas_max float8, berakning_konstant float8, berakning_referensniva float8, max_pejlbart_djup float8, fixpunkt varchar(20), enhet varchar(12), decimaler int2, skapad_datum timestamp, andrad_datum timestamp, andrad_av_id int4
MATOBJEKT (reader MSSQL_JDBC_NONSPATIAL_1)
    attributes: ID integer, TYP tinyint, NAMN nvarchar(60), AKTIV bit, KONTROLLPROGRAM bit, POS_N numeric(10,3), POS_E numeric(10,3), FASTIGHET nvarchar(60), LAGE nvarchar(500), BIFOGAD_BILD_ID integer, SKAPAD_DATUM smalldatetime, ANDRAD_DATUM datetime2, ANDRAD_AV_ID integer
    -> lowercase_20
lowercase_20: BulkAttributeRenamer
    ATTRCHOICE = All Attributes
    CASE_CHANGE_TYPE = lower
    MODE_CHOICE = RENAME
    PATTERN_ACTION_DISP = CASECHANGE
    -> matobjekt (writer POSTGRES_4)
matobjekt (writer POSTGRES_4)
    attributes: id int4, typ int2, namn varchar(60), aktiv bool, kontrollprogram bool, pos_n numeric(10,3), pos_e numeric(10,3), fastighet varchar(60), lage varchar(500), bifogad_bild_id int4, skapad_datum timestamp, andrad_datum timestamp, andrad_av_id int4
MATRUNDA (reader MSSQL_JDBC_NONSPATIAL_1)
    attributes: ID integer, NAMN nvarchar(60), AKTIV bit, BESKRIVNING nvarchar(500), SKAPAD_DATUM smalldatetime, ANDRAD_DATUM datetime2, ANDRAD_AV_ID integer
    -> lowercase_22
lowercase_22: BulkAttributeRenamer
    ATTRCHOICE = All Attributes
    CASE_CHANGE_TYPE = lower
    MODE_CHOICE = RENAME
    PATTERN_ACTION_DISP = CASECHANGE
    -> matrunda (writer POSTGRES_4)
matrunda (writer POSTGRES_4)
    attributes: id int4, namn varchar(60), aktiv bool, beskrivning varchar(500), skapad_datum timestamp, andrad_datum timestamp, andrad_av_id int4
MATRUNDA_MATNINGSTYP (reader MSSQL_JDBC_NONSPATIAL_1)
    attributes: MATRUNDA_ID integer, MATNINGSTYP_ID integer, ORDNING smallint
    -> lowercase_23
lowercase_23: BulkAttributeRenamer
    ATTRCHOICE = All Attributes
    CASE_CHANGE_TYPE = lower
    MODE_CHOICE = RENAME
    PATTERN_ACTION_DISP = CASECHANGE
    -> matrunda_matningstyp (writer POSTGRES_4)
matrunda_matningstyp (writer POSTGRES_4)
    attributes: matrunda_id int4, matningstyp_id int4, ordning int2
MEDDELANDEN_STARTSIDA (reader MSSQL_JDBC_NONSPATIAL_1)
    attributes: ID integer, DATUM smalldatetime, RUBRIK nvarchar(130), URL nvarchar(255), MEDDELANDE nvarchar(500), SKAPAD_DATUM smalldatetime, ANDRAD_DATUM datetime2, ANDRAD_AV_ID integer
    -> lowercase_24
lowercase_24: BulkAttributeRenamer
    ATTRCHOICE = All Attributes
    CASE_CHANGE_TYPE = lower
    MODE_CHOICE = RENAME
    PATTERN_ACTION_DISP = CASECHANGE
    -> meddelanden_startsida (writer POSTGRES_4)
meddelanden_startsida (writer POSTGRES_4)
    attributes: id int4, datum timestamp, rubrik varchar(130), url varchar(255), meddelande varchar(500), skapad_datum timestamp, andrad_datum timestamp, andrad_av_id int4
SYSTEMLOGG (reader MSSQL_JDBC_NONSPATIAL_1)
    attributes: ID bigint, LOGGAT_DATUM smalldatetime, LOGGAT_AV_ID integer, HANDELSE tinyint, BESKRIVNING nvarchar(500)
    -> lowercase_25
lowercase_25: BulkAttributeRenamer
    ATTRCHOICE = All Attributes
    CASE_CHANGE_TYPE = lower
    MODE_CHOICE = RENAME
    PATTERN_ACTION_DISP = CASECHANGE
    -> systemlogg (writer POSTGRES_4)
systemlogg (writer POSTGRES_4)
    attributes: id int8, loggat_datum timestamp, loggat_av_id int4, handelse int2, beskrivning varchar(500)

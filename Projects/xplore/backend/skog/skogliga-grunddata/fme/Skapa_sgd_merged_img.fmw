FME workspace Skapa_sgd_merged_img.fmw

Parameters:
- DIR_MERGED = c:\Data\skogliga_grunddata\sgd_vol_img
- DIR_VOL = \\fs-intra.metria.se\levlag\raster\skogliga_grunddata\volym_180320
- DIR_GY = \\fs-intra.metria.se\levlag\raster\skogliga_grunddata\grundyta_180320
- DIR_DGV = \\fs-intra.metria.se\levlag\raster\skogliga_grunddata\medeldiameter_180320
- DIR_HGV = \\fs-intra.metria.se\levlag\raster\skogliga_grunddata\medelhojd_180320
- min_x = 190000
- max_x = 1000000
- min_y = 6000000
- max_y = 6300000
- DIR_VOL_2_0 = C:\Data\Skogliga_grunddata_2_0\Leverans_20190903
- DIR_HGV_2_0 = C:\Data\Skogliga_grunddata_2_0\Leverans_20190903
- DIR_DGV_2_0 = C:\Data\Skogliga_grunddata_2_0\Leverans_20190903
- DIR_GY_2_0 = C:\Data\Skogliga_grunddata_2_0\Leverans_20190903
- SourceDataset_ESRISHAPE = C:\Data\Skogliga_grunddata_2_0\Leverans_20190903\rutorV20190828_BETA.shp   # Source Esri Shapefile(s)
- POSTGIS_HOST = pglag.vic-metria.nu   # POSTGIS Host
- POSTGIS_USER_NAME = c_geo   # POSTGIS Username
- POSTGIS_PASSWORD =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   # POSTGIS Password
- POSTGIS_PORT = 5432   # POSTGIS Port
- POSTGIS_DB = sks

Readers:
- ESRISHAPE_1: ESRISHAPE from $(SourceDataset_ESRISHAPE) in EPSG:3006

Writers:
- ERDAS_1: ERDAS to $(DIR_MERGED) in EPSG:3006

Creator
    GEOMTYPE = Geometry Object
    NUM = 1
    CREATED -> 2DBoxReplacer
2DBoxReplacer
    MAXYVALATTR = $(max_y)
    MAXXVALATTR = $(max_x)
    MINXVALATTR = $(min_x)
    MINYVALATTR = $(min_y)
    BOX -> AttributeKeeper
Note: Sökvägar till raster med skogliga grunddata: / Lokal PC: / DIR_VOL / \\fs-intra.metria.se\levlag\raster\skogliga_grunddata\volym_180320 / DIR_GY / \\fs-intra.metria.se\levlag\raster\skogliga_grunddata\grundyta_180320 / DIR_DGV / \\fs-intra.metria.se\levlag\raster\skogliga_grunddata\medeldiameter_180320 / DIR_HGV / \\fs-intra.metria.se\levlag\raster\skogliga_grunddata\medelhöjd / FME Server: / DIR_VOL / \\fs400.prodstod.se\levlag\raster\skogliga_grunddata\volym_180320 / DIR_GY / \\fs400.prodstod.se\levlag\raster\skogliga_grunddata\grundyta_180320 / DIR_DGV / \\fs400.prodstod.se\levlag\raster\skogliga_grunddata\medeldiameter_180320 / DIR_HGV / \\fs400.prodstod.se\levlag\raster\skogliga_grunddata\medelhöjd
AttributeKeeper
    -> FeatureReader [INITIATOR]
RasterBandCombiner
    ACCUM_ATTRS = Drop Incoming Attributes
    -> sgd_merge_img_2_0 (writer ERDAS_1)
sgd_merge_img_2_0 (writer ERDAS_1)

Bookmark: Välj rasterrutor för Skogliga grunddata 1.2
Note: Väljer ut rasterbilder som beör indatapolygonen
FeatureReader
    ATTRIBUTES = sks.skogligagrunddata_metadata_vol,"blockid,skannrutai,referensar,skanndatum,skanndat_1,skanndat_2,skanndat_3,lov_avlov,indexruta,produktion,variabel,version,skanner,enhet,relrmse,rmsehighvo,relrmse_hv,relrmse_lo,relrmse_ba,relbias_hv,relbias_lo,relbias_ba,rtytor_p,rtytor_t,epsg,bildformat,datatyp,lov,nodatavalu,producent,kommentar,shape_leng,shape_area,skann_omr,ruta"
    DATASET = $(POSTGIS_DB)
    ATTR_ACCUM_MODE = Only Use Result
    POSTGIS_DISABLE_COLLECTION_SPLITTING = yes
    POSTGIS_HOST = $(POSTGIS_HOST)
    POSTGIS_FEATURES_PER_FETCH = 10000
    FORMAT = POSTGIS
    POSTGIS_USER_NAME = $(POSTGIS_USER_NAME)
    POSTGIS_QUERY_FEATURE_TYPES_FOR_MERGE_FILTERS = Yes
    POSTGIS_USE_SEARCH_ENVELOPE = NO
    OUTPUT_FEATURES_DISPLAY = Schema and Data Features
    POSTGIS_PORT = $(POSTGIS_PORT)
    COMBINE_GEOM = Use Result
    INTERACT = Envelope Intersects
    COORDSYS = EPSG:3006
    FEATURETYPES = sks.skogligagrunddata_metadata_vol
    POSTGIS_PASSWORD = $(POSTGIS_PASSWORD)
    POSTGIS_USE_TRUE_POSTGIS_TYPES = yes
    sks.skogligagrunddata_metadata_vol -> AttributeKeeper_9
AttributeKeeper_9
    KEEP_ATTRS = indexruta
    -> DuplicateFilter
DuplicateFilter
    INPUT_ORDERED_CHOICE = No
    KEYATTR = indexruta
    UNIQUE -> Sorter
Sorter
    SORT_PARM = indexruta ALPHA ASCENDING
    SORTED -> StringConcatenator_3
    SORTED -> StringConcatenator_2
    SORTED -> StringConcatenator_4
    SORTED -> StringConcatenator_5

Bookmark: VOL
Note: Sätt ihop sträng med filnamn
StringConcatenator_4
    ACTION = Create New Attribute
    PARM_LINE = $(DIR_VOL)\VOL_@Value(indexruta).tif
    VAL_ATTR = DATASET
    -> FeatureReader_4 [INITIATOR]
Note: Läser ut rasterbilder som berör polygonen
FeatureReader_4
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    COORDSYS = EPSG:3006
    SUPPORTED_SPATIAL_INTERACTIONS = ENVELOPE_INTERSECT%INTERSECTS%CONTAINS%CROSSES%DISJOINT%EQUALS%OVERLAPS%TOUCHES%WITHIN
    FEATURETYPES = TIFF
    <OTHER> -> AttributeCreator
AttributeCreator
    ATTR_TABLE = SET_TO VERSION = 1
    -> Sorter_2
Note: Sätt ihop sträng med filnamn
StringConcatenator_6
    ACTION = Create New Attribute
    PARM_LINE = $(DIR_VOL_2_0)\VOL_20190829.tif
    VAL_ATTR = DATASET
    -> FeatureReader_6 [INITIATOR]
Note: Läser ut rasterbilder som berör polygonen
FeatureReader_6
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = Intersects
    COORDSYS = EPSG:3006
    SUPPORTED_SPATIAL_INTERACTIONS = ENVELOPE_INTERSECT%INTERSECTS%CONTAINS%CROSSES%DISJOINT%EQUALS%OVERLAPS%TOUCHES%WITHIN
    FEATURETYPES = TIFF
    <OTHER> -> Clipper_5 [CLIPPEE]
Note: Klipp rastret, utifrån den polygon som fås ur metadata
Clipper_5
    VAL_SOURCE = Clippee Only
    DEFAULT_VAL = 0
    ATTR_ACCUM_MODE = Merge Clipper
    MEASURE_TYPE = Continuous
    CREATE_AGGREGATES = Yes
    PRESERVE_CLIPPEE_EXTENTS = No
    MISSING_VAL_MODE = Compute
    LINES_AS_SEGMENTS = No
    CLIPPED_ATTR = _clipped
    ATTR_CONFLICT_RES = Use Clippee
    BOUNDARY_CASES = Treat as Inside
    CONNECT_Z_MODE = First Wins
    CLIP_TYPE = Multiple Clippers
    INSIDE -> RasterBandInterpretationCoercer
Note: Rastret är Int16
RasterBandInterpretationCoercer
    NUMERIC_TO_NUMERIC = Bounded cast
    FLOAT_TO_INTEGER = Round
    INTERPRETATION = Int16
    COLOR_TO_NUMERIC = Bounded cast
    -> RasterBandNodataSetter
Note: Sätt NodataValue, så att det överensstämmer med orginal-rastret
RasterBandNodataSetter
    REPLACE_CELL_VALUES = Yes
    NODATA_VALUE = -1
    -> AttributeCreator_2
AttributeCreator_2
    ATTR_TABLE = SET_TO VERSION = 2
    -> Sorter_2
Sorter_2
    SORT_PARM = VERSION NUMERIC ASCENDING
    SORTED -> RasterMosaicker
RasterMosaicker
    SNAPPING_TYPE_NAME = Resample
    MERGE_PALETTES_NAME = Yes
    OVERLAPPING_VALUES = last
    INTERPOLATION_TYPE_NAME = Nearest Neighbor
    ACCUM_ATTRS_NAME = Merge Incoming Attributes
    NODATA_OVERWRITE = No
    -> AttributeKeeper_2
AttributeKeeper_2
    -> RasterBandNameSetter_2
Note: Sätt namn på bandet
RasterBandNameSetter_2
    BAND_NAME = VOL
    INPUT_TYPE = Single Name
    -> RasterBandCombiner

Bookmark: GY
Note: Sätt ihop sträng med filnamn
StringConcatenator_3
    ACTION = Create New Attribute
    PARM_LINE = $(DIR_GY)\GY_@Value(indexruta).tif
    VAL_ATTR = DATASET
    -> FeatureReader_2 [INITIATOR]
Note: Läser ut rasterbilder som berör polygonen
FeatureReader_2
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Sorter_4
Note: Sätt ihop sträng med filnamn
StringConcatenator_7
    ACTION = Create New Attribute
    PARM_LINE = $(DIR_GY_2_0)\BA_20190829.tif
    VAL_ATTR = DATASET
    -> FeatureReader_7 [INITIATOR]
Note: Läser ut rasterbilder som berör polygonen
FeatureReader_7
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Clipper_2 [CLIPPEE]
Note: Klipp rastret, utifrån den polygon som fås ur metadata
Clipper_2
    VAL_SOURCE = Clippee Only
    DEFAULT_VAL = 0
    ATTR_ACCUM_MODE = Merge Clipper
    MEASURE_TYPE = Continuous
    CREATE_AGGREGATES = Yes
    PRESERVE_CLIPPEE_EXTENTS = No
    MISSING_VAL_MODE = Compute
    LINES_AS_SEGMENTS = No
    CLIPPED_ATTR = _clipped
    ATTR_CONFLICT_RES = Use Clippee
    BOUNDARY_CASES = Treat as Inside
    CONNECT_Z_MODE = First Wins
    CLIP_TYPE = Multiple Clippers
    INSIDE -> RasterBandInterpretationCoercer_2
Note: Rastret är Int16
RasterBandInterpretationCoercer_2
    NUMERIC_TO_NUMERIC = Bounded cast
    FLOAT_TO_INTEGER = Round
    INTERPRETATION = Int16
    COLOR_TO_NUMERIC = Bounded cast
    -> RasterBandNodataSetter_2
Note: Sätt NodataValue, så att det överensstämmer med orginal-rastret
RasterBandNodataSetter_2
    REPLACE_CELL_VALUES = Yes
    NODATA_VALUE = -1
    -> AttributeCreator_4
AttributeCreator_4
    ATTR_TABLE = SET_TO VERSION = 2
    -> Sorter_4
Sorter_4
    SORT_PARM = VERSION NUMERIC ASCENDING
    SORTED -> RasterMosaicker_2
RasterMosaicker_2
    SNAPPING_TYPE_NAME = Resample
    MERGE_PALETTES_NAME = Yes
    OVERLAPPING_VALUES = last
    INTERPOLATION_TYPE_NAME = Nearest Neighbor
    ACCUM_ATTRS_NAME = Merge Incoming Attributes
    NODATA_OVERWRITE = No
    -> AttributeKeeper_3
AttributeKeeper_3
    -> RasterBandNameSetter
Note: Sätt namn på bandet
RasterBandNameSetter
    BAND_NAME = GY
    INPUT_TYPE = Single Name
    -> RasterBandCombiner

Bookmark: DGV
Note: Sätt ihop sträng med filnamn
StringConcatenator_2
    ACTION = Create New Attribute
    PARM_LINE = $(DIR_DGV)\DGV_@Value(indexruta).tif
    VAL_ATTR = DATASET
    -> FeatureReader_3 [INITIATOR]
Note: Läser ut rasterbilder som berör polygonen
FeatureReader_3
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Sorter_3
Note: Sätt ihop sträng med filnamn
StringConcatenator_8
    ACTION = Create New Attribute
    PARM_LINE = $(DIR_DGV_2_0)\DGV_20190829.tif
    VAL_ATTR = DATASET
    -> FeatureReader_8 [INITIATOR]
Note: Läser ut rasterbilder som berör polygonen
FeatureReader_8
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Clipper_3 [CLIPPEE]
Note: Klipp rastret, utifrån den polygon som fås ur metadata
Clipper_3
    VAL_SOURCE = Clippee Only
    DEFAULT_VAL = 0
    ATTR_ACCUM_MODE = Merge Clipper
    MEASURE_TYPE = Continuous
    CREATE_AGGREGATES = Yes
    PRESERVE_CLIPPEE_EXTENTS = No
    MISSING_VAL_MODE = Compute
    LINES_AS_SEGMENTS = No
    CLIPPED_ATTR = _clipped
    ATTR_CONFLICT_RES = Use Clippee
    BOUNDARY_CASES = Treat as Inside
    CONNECT_Z_MODE = First Wins
    CLIP_TYPE = Multiple Clippers
    INSIDE -> RasterBandInterpretationCoercer_3
Note: Rastret är Int16
RasterBandInterpretationCoercer_3
    NUMERIC_TO_NUMERIC = Bounded cast
    FLOAT_TO_INTEGER = Round
    INTERPRETATION = Int16
    COLOR_TO_NUMERIC = Bounded cast
    -> RasterBandNodataSetter_3
Note: Sätt NodataValue, så att det överensstämmer med orginal-rastret
RasterBandNodataSetter_3
    REPLACE_CELL_VALUES = Yes
    NODATA_VALUE = -1
    -> AttributeCreator_3
AttributeCreator_3
    ATTR_TABLE = SET_TO VERSION = 2
    -> Sorter_3
Sorter_3
    SORT_PARM = VERSION NUMERIC ASCENDING
    SORTED -> RasterMosaicker_3
RasterMosaicker_3
    SNAPPING_TYPE_NAME = Resample
    MERGE_PALETTES_NAME = Yes
    OVERLAPPING_VALUES = last
    INTERPOLATION_TYPE_NAME = Nearest Neighbor
    ACCUM_ATTRS_NAME = Merge Incoming Attributes
    NODATA_OVERWRITE = No
    -> AttributeKeeper_6
AttributeKeeper_6
    -> RasterBandNameSetter_3
Note: Sätt namn på bandet
RasterBandNameSetter_3
    BAND_NAME = DGV
    INPUT_TYPE = Single Name
    -> RasterBandCombiner

Bookmark: HGV
Note: Sätt ihop sträng med filnamn
StringConcatenator_5
    ACTION = Create New Attribute
    PARM_LINE = $(DIR_HGV)\HGV_@Value(indexruta).tif
    VAL_ATTR = DATASET
    -> FeatureReader_5 [INITIATOR]
Note: Läser ut rasterbilder som berör polygonen
FeatureReader_5
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Sorter_5
Note: Sätt ihop sträng med filnamn
StringConcatenator_9
    ACTION = Create New Attribute
    PARM_LINE = $(DIR_HGV_2_0)\HGV_20190829.tif
    VAL_ATTR = DATASET
    -> FeatureReader_9 [INITIATOR]
Note: Läser ut rasterbilder som berör polygonen
FeatureReader_9
    DATASET = @Value(DATASET)
    ATTR_ACCUM_MODE = Only Use Result
    TIFF_FEATURE_TYPE_NAME = FORMAT_NAME
    TIFF_USE_SEARCH_ENVELOPE = NO
    FORMAT = TIFF
    OUTPUT_FEATURES_DISPLAY = Schema and Data Features
    TIFF_READER_META_ATTRIBUTES = fme_dataset fme_basename
    COMBINE_GEOM = Use Result
    INTERACT = <No Spatial Filter>
    SUPPORTED_SPATIAL_INTERACTIONS = ENVELOPE_INTERSECT%INTERSECTS%CONTAINS%CROSSES%DISJOINT%EQUALS%OVERLAPS%TOUCHES%WITHIN
    FEATURETYPES = TIFF
    <OTHER> -> Clipper_4 [CLIPPEE]
Note: Klipp rastret, utifrån den polygon som fås ur metadata
Clipper_4
    VAL_SOURCE = Clippee Only
    DEFAULT_VAL = 0
    ATTR_ACCUM_MODE = Merge Clipper
    MEASURE_TYPE = Continuous
    CREATE_AGGREGATES = Yes
    PRESERVE_CLIPPEE_EXTENTS = No
    MISSING_VAL_MODE = Compute
    LINES_AS_SEGMENTS = No
    CLIPPED_ATTR = _clipped
    ATTR_CONFLICT_RES = Use Clippee
    BOUNDARY_CASES = Treat as Inside
    CONNECT_Z_MODE = First Wins
    CLIP_TYPE = Multiple Clippers
    INSIDE -> RasterBandInterpretationCoercer_4
Note: Rastret är Int16
RasterBandInterpretationCoercer_4
    NUMERIC_TO_NUMERIC = Bounded cast
    FLOAT_TO_INTEGER = Round
    INTERPRETATION = Int16
    COLOR_TO_NUMERIC = Bounded cast
    -> RasterBandNodataSetter_4
Note: Sätt NodataValue, så att det överensstämmer med orginal-rastret
RasterBandNodataSetter_4
    REPLACE_CELL_VALUES = Yes
    NODATA_VALUE = -1
    -> AttributeCreator_5
AttributeCreator_5
    ATTR_TABLE = SET_TO VERSION = 2
    -> Sorter_5
Sorter_5
    SORT_PARM = VERSION NUMERIC ASCENDING
    SORTED -> RasterMosaicker_4
RasterMosaicker_4
    SNAPPING_TYPE_NAME = Resample
    MERGE_PALETTES_NAME = Yes
    OVERLAPPING_VALUES = last
    INTERPOLATION_TYPE_NAME = Nearest Neighbor
    ACCUM_ATTRS_NAME = Merge Incoming Attributes
    NODATA_OVERWRITE = No
    -> AttributeKeeper_7
AttributeKeeper_7
    -> RasterBandNameSetter_4
Note: Sätt namn på bandet
RasterBandNameSetter_4
    BAND_NAME = HGV
    INPUT_TYPE = Single Name
    -> RasterBandCombiner

Bookmark: Välj rasterrutor för Skogliga grunddata 2.0
rutorV20190828_BETA (reader ESRISHAPE_1)
    attributes: id char(254), datum char(254), kommentar char(254), flyghojd char(254), flyghastig char(254), overtackni char(254), punkttathe char(254), skannerid char(254), skannerfab char(254), skannermod char(254), oppningsvi char(254), pulsfrekve char(254), skanningsf char(254), uteffekt char(254), square char(254), Block char(254), SkannDat char(254), N char(254), E char(254), Las_Namn char(254), Skanner2 double, Region double, LOV_AVL double
    -> Dissolver
Dissolver
    ACCUM_INPUT_ATTRS = Use Attributes From One Feature
    DEAGGREGATE_INPUT = Yes
    NO_OVRLP = No
    CONNECT_Z_MODE = First Wins
    AREA -> Aggregator
Aggregator
    PRESERVE_ID = No
    AGGREGATE_TYPE = Homogeneous Collection (If Possible)
    MODE = Geometry - Assemble One Level
    ORDERED = No
    ATTR_TO_TRAIT = Yes
    SEP = ,
    ACCUM_ATTRS_NAME = Use Attributes From One Feature
    ID_SELECTION = ID and Parent ID
    AGGREGATE -> BoundingBoxAccumulator
    AGGREGATE -> Clipper_5 [CLIPPER]
    AGGREGATE -> Clipper_2 [CLIPPER]
    AGGREGATE -> StringConcatenator_9
BoundingBoxAccumulator
    SOURCE_SCALE = 1
    ATTR_NAME = _topferIndex
    DESTINATION_SCALE = 1
    ACCUM_ATTRS_NAME = Use Attributes From One Feature
    TOPFER_INDEX = No
    BOUNDING_BOX -> StringConcatenator_6
    BOUNDING_BOX -> StringConcatenator_7
    BOUNDING_BOX -> StringConcatenator_8
    BOUNDING_BOX -> Clipper_3 [CLIPPER]
    BOUNDING_BOX -> Clipper_4 [CLIPPER]

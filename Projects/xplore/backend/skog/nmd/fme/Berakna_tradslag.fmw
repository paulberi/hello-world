FME workspace Berakna_tradslag.fmw

Parameters:
- polygon =   # Polygon
- bbox =
- fastighet =
- fastighetsdelomrade =
- DestDataset_JSON = C:\temp\tradslag_info.json   # Destination JSON (JavaScript Object Notation) File
- MAX_AREAL_HA = 10000
- MAX_BRYTPUNKTER = 2000
- POSTGIS_HOST = pglag.vic-metria.nu   # POSTGIS Host
- POSTGIS_USER_NAME = c_geo   # POSTGIS Username
- POSTGIS_PASSWORD =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   # POSTGIS Password
- POSTGIS_PORT = 5432   # POSTGIS Port
- SourceDataset_GEOTIFF = \\fs400.prodstod.se\levlag\raster\Nationell_Marktacke_Data\Basskikt\nmd2018bas_ogeneraliserad_v1_0.tif   # Source GeoTIFF File(s)
- DATASET = D:\FME_Work_Files\GemensamResurs\Nationell_Marktacke_Data\nmd2018bas_ogeneraliserad_v1_0.img   # "" Dataset

Readers:
- GEOTIFF_1: GEOTIFF from $(SourceDataset_GEOTIFF) in EPSG:3006

Writers:
- JSON_1: JSON to $(DestDataset_JSON)

Note: Hårdkodning av Referensår och Avverkningsrevidering
AttributeCreator_3
    ATTR_TABLE = SET_TO referensAr = 2018
    -> Trädslagsfördelning (writer JSON_1)
    -> AttributeCreator_3_Output
Note: raster_stats: raster_stats [JSON]
Trädslagsfördelning (writer JSON_1)
    attributes: tallskogHa float, granskogHa float, barrblandskogHa float, lovblandadBarrskogHa float, triviallovHa float, adellovHa float, triviallovAdellovHa float, temporartEjSkogHa float, skogHa float, skogVatmarkHa float, oppenVatmarkHa float, akermarkHa float, ovrigOppenMarkHa float, exploateradMarkHa float, vattenHa float, molnOklassatHa float, Areal_raster_ha float, Area_ha float, referensAr int, raster_status string
Note: Lokal disk på fme server: / D:\FME_Work_Files\GemensamResurs\Nationell_Marktacke_Data\nmd2018bas_ogeneraliserad_v1_0.img
Note: FME desktop - PC: / \\fs-intra.metria.se\levlag\raster\Nationell_Marktacke_Data\Basskikt\nmd2018bas_ogeneraliserad_v1_0.tif / \\fs-intra.metria.se\levlag\raster\Nationell_Marktacke_Data\Basskikt\img\nmd2018bas_ogeneraliserad_v1_0.img / FME Server - test / \\fs400.prodstod.se\levlag\raster\Nationell_Marktacke_Data\Basskikt\nmd2018bas_ogeneraliserad_v1_0.tif / FME Server - test (lila nätet) / \\fs600.vic-metria.nu\levlag\raster\Nationell_Marktacke_Data\Basskikt\nmd2018bas_ogeneraliserad_v1_0.tif / FME Server - produktion / \\fs40.vic-metria.nu\levlag\raster\Nationell_Marktacke_Data\Basskikt\nmd2018bas_ogeneraliserad_v1_0.tif
AttributeCreator_3_Output: Logger
    LOG_FEATURE = LOG_RECORD
    MAXCOORDS = 20
    MAXFEATS = 20
    MESSAGE = Feature is:
    SEVERITY = INFO

Bookmark: Indata WKT Geometry
Creator_2
    COORDSYS = EPSG:3006
    GEOM = <?xml version="1.0" encoding="US_ASCII" standalone="no" ?><geometry><point><coord x="1" y="1"/></point></geometry>
    GEOMTYPE = Geometry Object
    NUM = 1
    CREATED -> TestFilter
TestFilter
    DEFAULT_VALUE = <UNFILTERED>
    TEST_LIST = "BOOL_OP,OR,COMPOSITE_TEST,""""""1"""""",TEST_CLAUSE,TEST $(polygon) != """,Polygon har ett värde,"BOOL_OP,OR,COMPOSITE_TEST,""""""1"""""",TEST_CLAUSE,TEST $(fastighet) != """,Fastighet har ett värde,"BOOL_OP,OR,COMPOSITE_TEST,""""""1"""""",TEST_CLAUSE,TEST $(fastighetsdelomrade) != """,Fastighetsdelområde har ett värde
    Polygon har ett värde -> Tester_2
    Fastighet har ett värde -> Tester_10
    Fastighetsdelområde har ett värde -> FeatureReader_2 [INITIATOR]
    <UNFILTERED> -> Terminator_8
Note: Kontrollera om parametern fastighet innehåller fnutt
Tester_10
    BOOL_OP = OR
    COMPOSITE_TEST = 1
    TEST_CLAUSE = CASE_INSENSITIVE_TEST $(fastighet) CONTAINS '
    TEST_MODE = CASE_INSENSITIVE_TEST
    PASSED -> FeatureReader_3 [INITIATOR]
    FAILED -> FeatureReader [INITIATOR]
Terminator_8
    MESSAGE = Antingen fastighet eller polygon måste ha ett värde
AttributeKeeper_8
    KEEP_ATTRS = _polygon
    -> GeometryValidator
Note: Kontrollera geometrin
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]FME_CONTROLLER_QUERY_FILE]transformers\dependencies\geometryvalidator\SELF_INTERSECTING.fme OGC_VALID_CHECK OGC_VERSION]V1.2.0]FME_CONTROLLER_QUERY_FILE]transformers/dependencies/geometryvalidator/OGC_VALID_CHECK.fme
    SUMMARY = Brief
    PASSED -> AreaCalculator
    FAILED -> Deaggregator_3
    REPAIRED -> AreaCalculator
    <REJECTED> -> GeometryRemover_2
GeometryRemover_2
    -> Terminator_4
Terminator_4
    MESSAGE = Felaktig geometri
Cloner
    COPIES = 1
    COPYATT = _copynum
    COPY -> AreaCalculator
AreaCalculator
    AREA_ATTR = Areal_wkt
    AREA_TYPE = Plane Area
    MULT = 1
    -> m2_till_hektar_2
Note: Areal_wkt_ha
m2_till_hektar_2: ExpressionEvaluator
    ACTION = Create New Attribute
    EXPRESSION = @mult(@Value(Areal_wkt),0.0001)
    VAL_ATTR = Areal_wkt_ha
    -> Tester_5
Note: Tillåt endast ytor som har färre än 1000 brytpunkter
Tester_5
    BOOL_OP = OR
    COMPOSITE_TEST = 1
    TEST_CLAUSE = TEST @Evaluate(@NumCoords(FLATTEN_AGGREGATE)) < $(MAX_BRYTPUNKTER)
    TEST_MODE = TEST
    PASSED -> Tester
    FAILED -> GeometryRemover_3
Note: Tillåt endast ytor som är mindre än 10 000 ha
Tester
    BOOL_OP = OR
    COMPOSITE_TEST = 1
    TEST_CLAUSE = TEST @Value(Areal_wkt_ha) < $(MAX_AREAL_HA)
    TEST_MODE = TEST
    PASSED -> AttributeKeeper_6
    PASSED -> AttributeKeeper_5
    PASSED -> FeatureReader_4 [INITIATOR]
    FAILED -> Terminator
Terminator
    MESSAGE = Endast ytor mindre än 10 000 ha är tillåtna
GeometryRemover_3
    -> Terminator_7
Terminator_7
    MESSAGE = För många brytp
GeometryRemover_12
    -> Terminator_11
Terminator_11
    MESSAGE = Felaktig geometri

Bookmark: Polygon
Note: Kontrollera att polygon har ett värde
Tester_2
    BOOL_OP = OR
    COMPOSITE_TEST = 1
    TEST_CLAUSE = TEST $(polygon) != ""
    TEST_MODE = TEST
    PASSED -> GeometryReplacer
    FAILED -> Terminator_3
GeometryReplacer
    KIND_LONG = OGC Well Known Text
    OGC_WKT_PRECISION_DISPLAY = 64-bit
    REMOVE_ATTRIBUTE = Yes
    SOURCE = $(polygon)
    -> ParameterFetcher
    <REJECTED> -> Terminator_2
ParameterFetcher
    ATTR_LIST = _polygon $(polygon)
    -> AttributeKeeper_8
Terminator_2
    MESSAGE = Polygon saknar värde
Terminator_3
    MESSAGE = Polygon saknar värde

Bookmark: Endast en fastighet - utan enkelfnutt
Note: Slå upp fastighetsytorna mot AY_FAST i geodatalagret
FeatureReader
    ATTRIBUTES = lm.AY_FAST,"FNR_FDS,EXTERNID,DETALJTYP,KOMMUNKOD,KOMMUNNAMN,TRAKT,BLOCKENHET,OMRNR,FASTIGHET,YTKVAL,ADAT,OBJECTID,OMRTYP,OBJEKT_ID"
    ATTR_ACCUM_MODE = Only Use Result
    COMBINE_GEOM = Use Result
    DATASET = lm26
    FEATURETYPES = lm.AY_FAST
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(POSTGIS_HOST)
    POSTGIS_PASSWORD = $(POSTGIS_PASSWORD)
    POSTGIS_PORT = $(POSTGIS_PORT)
    POSTGIS_QUERY_FEATURE_TYPES_FOR_MERGE_FILTERS = Yes
    POSTGIS_USER_NAME = $(POSTGIS_USER_NAME)
    POSTGIS_USE_SEARCH_ENVELOPE = NO
    POSTGIS_USE_TRUE_POSTGIS_TYPES = yes
    WHERE = "OBJEKT_ID" = '$(fastighet)'
    lm.AY_FAST -> AttributeKeeper_2
    <REJECTED> -> Terminator_5
AttributeKeeper_2
    KEEP_ATTRS = OBJEKT_ID
    -> Deaggregator
Note: Deggregera för att sedan kunna aggregera till en multipolygon istället för en geometrycollection
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Aggregator_2
Aggregator_2
    ACCUM_ATTRS_NAME = Use Attributes From One Feature
    AGGREGATE_TYPE = Homogeneous Collection (If Possible)
    GROUP_BY = OBJEKT_ID
    MODE = Geometry - Assemble One Level
    SEP = ,
    AGGREGATE -> GeometryExtractor
GeometryExtractor
    ATTR = _polygon
    KIND_LONG = OGC Well Known Text
    OGCVERSION = 1.2
    OGC_WKT_PRECISION_DISPLAY = 64-bit
    PREFER_POLYGON_OVER_SURFACE = No
    REMOVE_GEOMETRY = No
    -> AttributeKeeper_8
Terminator_5
    MESSAGE = Ingen kontakt med databasen. Var vänlig kontakta supporten.

Bookmark: Kommaseparerad lista med en eller flera fastigheter - fastigheterna har enkelfnutt
Note: Slå upp fastighetsytorna mot AY_FAST i geodatalagret
FeatureReader_3
    ATTRIBUTES = lm.AY_FAST,"FNR_FDS,EXTERNID,DETALJTYP,KOMMUNKOD,KOMMUNNAMN,TRAKT,BLOCKENHET,OMRNR,FASTIGHET,YTKVAL,ADAT,OBJECTID,OMRTYP,OBJEKT_ID"
    ATTR_ACCUM_MODE = Only Use Result
    COMBINE_GEOM = Use Result
    DATASET = lm26
    FEATURETYPES = lm.AY_FAST
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(POSTGIS_HOST)
    POSTGIS_PASSWORD = $(POSTGIS_PASSWORD)
    POSTGIS_PORT = $(POSTGIS_PORT)
    POSTGIS_QUERY_FEATURE_TYPES_FOR_MERGE_FILTERS = Yes
    POSTGIS_USER_NAME = $(POSTGIS_USER_NAME)
    POSTGIS_USE_SEARCH_ENVELOPE = NO
    POSTGIS_USE_TRUE_POSTGIS_TYPES = yes
    WHERE = "OBJEKT_ID" IN ($(fastighet))
    lm.AY_FAST -> AttributeKeeper_9
    <REJECTED> -> Terminator_10
Note: Deggregera för att sedan kunna aggregera till en multipolygon istället för en geometrycollection
AttributeKeeper_9
    KEEP_ATTRS = OBJEKT_ID
    -> Deaggregator_2
Note: Deggregera för att sedan kunna aggregera till en multipolygon istället för en geometrycollection
Deaggregator_2
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Aggregator_4
Aggregator_4
    ACCUM_ATTRS_NAME = Use Attributes From One Feature
    AGGREGATE_TYPE = Homogeneous Collection (If Possible)
    MODE = Geometry - Assemble One Level
    SEP = ,
    AGGREGATE -> GeometryExtractor_3
GeometryExtractor_3
    ATTR = _polygon
    KIND_LONG = OGC Well Known Text
    OGCVERSION = 1.2
    OGC_WKT_PRECISION_DISPLAY = 64-bit
    PREFER_POLYGON_OVER_SURFACE = No
    REMOVE_GEOMETRY = No
    -> AttributeKeeper_8
Terminator_10
    MESSAGE = Ingen kontakt med databasen. Var vänlig kontakta supporten.

Bookmark: Ett fastighetsdelområde eller kommaseparerad lista med flera fastighetsdelområden
Note: Slå upp fastighetsytorna mot AY_FAST i geodatalagret
FeatureReader_2
    ATTRIBUTES = lm.AY_FAST,"FNR_FDS,EXTERNID,DETALJTYP,KOMMUNKOD,KOMMUNNAMN,TRAKT,BLOCKENHET,OMRNR,FASTIGHET,YTKVAL,ADAT,OBJECTID,OMRTYP,OBJEKT_ID"
    ATTR_ACCUM_MODE = Only Use Result
    COMBINE_GEOM = Use Result
    DATASET = lm26
    FEATURETYPES = lm.AY_FAST
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(POSTGIS_HOST)
    POSTGIS_PASSWORD = $(POSTGIS_PASSWORD)
    POSTGIS_PORT = $(POSTGIS_PORT)
    POSTGIS_QUERY_FEATURE_TYPES_FOR_MERGE_FILTERS = Yes
    POSTGIS_USER_NAME = $(POSTGIS_USER_NAME)
    POSTGIS_USE_SEARCH_ENVELOPE = NO
    POSTGIS_USE_TRUE_POSTGIS_TYPES = yes
    WHERE = "OBJECTID" IN ($(fastighetsdelomrade))
    lm.AY_FAST -> AttributeKeeper_7
    <REJECTED> -> Terminator_9
AttributeKeeper_7
    KEEP_ATTRS = OBJECTID
    -> Deaggregator_4
Deaggregator_4
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Aggregator_5
Aggregator_5
    ACCUM_ATTRS_NAME = Use Attributes From One Feature
    AGGREGATE_TYPE = Homogeneous Collection (If Possible)
    MODE = Geometry - Assemble One Level
    SEP = ,
    AGGREGATE -> GeometryExtractor_2
GeometryExtractor_2
    ATTR = _polygon
    KIND_LONG = OGC Well Known Text
    OGCVERSION = 1.2
    OGC_WKT_PRECISION_DISPLAY = 64-bit
    PREFER_POLYGON_OVER_SURFACE = No
    REMOVE_GEOMETRY = No
    -> AttributeKeeper_8
Terminator_9
    MESSAGE = Ingen kontakt med databasen. Var vänlig kontakta supporten.

Bookmark: Försök reparera geometrin
Deaggregator_3
    EXPLODE_INSTANCES = No
    GEOM_NAME_FIELD = _geometry_name
    LIST_ATTR_MODE_LOOKUP = LEAN
    MODE = Flatten All Levels
    SPLIT_COMPOSITES = No
    DEAGGREGATED -> AreaGapAndOverlapCleaner
AreaGapAndOverlapCleaner
    CLEANING_TOLERANCE = Automatic
    CONNECT_Z_MODE = First Wins
    DEAGGREGATE_INPUT = YES
    FILL_ALL_GAPS = No
    MEASURE_TYPE = Continuous
    MISSING_VAL_MODE = Compute
    REPAIR_METHOD = Longest Boundary
    REPAIRED -> Dissolver_2
Dissolver_2
    ACCUM_INPUT_ATTRS = Use Attributes From One Feature
    CLEANING_TOLERANCE = Automatic
    CONNECT_Z_MODE = First Wins
    DEAGGREGATE_INPUT = Yes
    AREA -> SpikeRemover
SpikeRemover
    DIMENSIONS = 2D
    ITERATIVE = Yes
    SPIKEANGLE = 5
    SPIKELENGTH = 100
    UNCHANGED -> Aggregator_3
    CHANGED -> Aggregator_3
Aggregator_3
    ACCUM_ATTRS_NAME = Use Attributes From One Feature
    AGGREGATE_TYPE = Homogeneous Collection (If Possible)
    MODE = Geometry - Assemble One Level
    SEP = ,
    AGGREGATE -> GeometryValidator_3
Note: Kontrollera geometrin
GeometryValidator_3
    ISSUE_ATTR_NAME = _issues
    PRESETS = Custom
    REPAIR = No
    RULES = SELF_INTERSECTING CHECK_HOLE_TOUCHING_POLYGON]Yes]CONNECT_Z_MODE_SI]IGNORE_Z]SELF_INTERSECTION_TOLERANCE]Automatic]FME_CONTROLLER_QUERY_FILE]transformers\dependencies\geometryvalidator\SELF_INTERSECTING.fme OGC_VALID_CHECK OGC_VERSION]V1.2.0]FME_CONTROLLER_QUERY_FILE]transformers/dependencies/geometryvalidator/OGC_VALID_CHECK.fme
    SUMMARY = Detailed
    PASSED -> Cloner
    FAILED -> Clipper_3 [CLIPPEE]
    REPAIRED -> Cloner
    ISSUE_LOCATIONS -> Bufferer
    <REJECTED> -> GeometryRemover_12

Bookmark: Försök igen med att reparera geometrier med self-intersectors som geometryvalidator och areaGapAndOverlapcleaner inte lyckas reparera
Bufferer
    ANGLE = 22.5
    CAP_STYLE = Round
    CORNER_STYLE = Round
    MODE = AREA
    OFFSET = 1
    OFFSET_UNITS = NONE
    BUFFERED -> Clipper_3 [CLIPPER]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> GeometryValidator_2
Note: Kontrollera geometrin
GeometryValidator_2
    ISSUE_ATTR_NAME = _issues
    PRESETS = Custom
    REPAIR = No
    RULES = SELF_INTERSECTING CHECK_HOLE_TOUCHING_POLYGON]Yes]CONNECT_Z_MODE_SI]IGNORE_Z]SELF_INTERSECTION_TOLERANCE]Automatic]FME_CONTROLLER_QUERY_FILE]transformers\dependencies\geometryvalidator\SELF_INTERSECTING.fme OGC_VALID_CHECK OGC_VERSION]V1.2.0]FME_CONTROLLER_QUERY_FILE]transformers/dependencies/geometryvalidator/OGC_VALID_CHECK.fme
    SUMMARY = Detailed
    PASSED -> Cloner
    FAILED -> GeometryRemover_12
    REPAIRED -> Cloner
    <REJECTED> -> GeometryRemover_12

Bookmark: Overlay av polygon mot rastret, omvandling till punktmoln och klippning mot punktmoln
AttributeKeeper_5
    KEEP_ATTRS = Areal_wkt_ha
    -> Clipper_4 [CLIPPER]
AttributeKeeper_6
    KEEP_ATTRS = Areal_wkt_ha
    -> Clipper [CLIPPER]
Note: Läs upp den del av rastret som intersectar mot den polygon som är input
FeatureReader_4
    ATTRIBUTES = ERDAS,
    ATTR_ACCUM_MODE = Only Use Result
    COMBINE_GEOM = Use Result
    DATASET = $(DATASET)
    ERDAS_GROUP_BY_DATASET = No
    ERDAS_READER_META_ATTRIBUTES = fme_basename
    ERDAS_USE_SEARCH_ENVELOPE = NO
    FEATURETYPES = ERDAS
    FORMAT = ERDAS
    INTERACT = Initiator Intersects Result
    OUTPUT_FEATURES_DISPLAY = Schema and Data Features
    ERDAS -> RasterPaletteRemover
Note: GEOTIFF: nmd2018bas_ogeneraliserad_v1_0 [GEOTIFF]
GEOTIFF (reader GEOTIFF_1)
    -> RasterPaletteRemover
Note: Ta bort rasterpalette
RasterPaletteRemover
    -> Clipper [CLIPPEE]
Note: Klipp rastret med den polygon som är input
Clipper
    ATTR_ACCUM_MODE = Merge Clipper
    ATTR_CONFLICT_RES = Use Clippee
    BOUNDARY_CASES = Treat as Inside
    CLEANING_TOLERANCE = None
    CLIPPED_ATTR = _clipped
    CLIP_TYPE = Single Clipper
    LINES_AS_SEGMENTS = No
    MEASURE_TYPE = Continuous
    MISSING_VAL_MODE = Compute
    PRESERVE_CLIPPEE_EXTENTS = No
    VAL_SOURCE = Clippee Only
    INSIDE -> PointCloudCombiner
Note: Gör om till punktmoln
PointCloudCombiner
    ACCUM_ATTRS_NAME = No
    EXTRACT_RASTER_NODATA_NAME = No
    SPACING = 1.0
    -> Clipper_4 [CLIPPEE]
    <REJECTED> -> Terminator_6
Note: Klipp punktmolnet med den polygon som är input
Clipper_4
    ATTR_ACCUM_MODE = Merge Clipper
    ATTR_CONFLICT_RES = Use Clippee
    BOUNDARY_CASES = Treat as Inside
    CLEANING_TOLERANCE = None
    CLIPPED_ATTR = _clipped
    CLIP_TYPE = Single Clipper
    CONNECT_Z_MODE = First Wins
    LINES_AS_SEGMENTS = No
    MEASURE_TYPE = Continuous
    MISSING_VAL_MODE = Compute
    PRESERVE_CLIPPEE_EXTENTS = No
    VAL_SOURCE = Clipper and Clippee
    INSIDE -> PointCloudPropertyExtractor
    <REJECTED> -> Clipper_4__Rejected_
Clipper_4__Rejected_: Logger
    LOG_FEATURE = LOG_RECORD
    MAXCOORDS = 20
    MAXFEATS = 20
    MESSAGE = Feature is:
    SEVERITY = INFO
Terminator_6
    MESSAGE = Kan ej göra om raster till punktmoln

Bookmark: Beräkningar på punktmolnet
Note: Ta ut totala antalet punkter
PointCloudPropertyExtractor
    CALCULATE_EXTENTS_DISPLAY = No
    POINT_COMPONENTS = "env  PROPERTIES "
    -> Tester_4
Note: Kontrollera att antalet punkter > 0
Tester_4
    BOOL_OP = OR
    COMPOSITE_TEST = 1
    TEST_CLAUSE = TEST @Value(_num_points) > 0
    TEST_MODE = TEST
    PASSED -> PointCloudComponentRenamer_2
Note: Döp om komponenterna i punktmolnet, då banden hamnar på färgerna istället för bandnummer.
PointCloudComponentRenamer_2
    COMPONENTS_TO_RENAME = z,env
    -> AttributeRenamer_3
AttributeRenamer_3
    ATTR_TABLE = RENAME_SET_DEFAULT _num_points > tot_num_points
    -> AttributeCreator_6
    -> PointCloudSplitter
AttributeCreator_6
    ATTR_TABLE = SET_TO id = 1
    -> AttributeKeeper_4
AttributeKeeper_4
    KEEP_ATTRS = id,tot_num_points,Areal_wkt_ha
    -> ExpressionEvaluator
Note: Beräkna Total rasterarea för området
ExpressionEvaluator
    ACTION = Create New Attribute
    EXPRESSION = @mult(0.01,@Value(tot_num_points))
    VAL_ATTR = Areal_raster_ha
    -> Tester_3
Note: Kontrollera att rastrets areal är som polygonens areal med +- 10 %. / I annat fall kan man anse att polygonen ligger delvis utanför rastrets extent.
Tester_3
    BOOL_OP = OR
    COMPOSITE_TEST = 1
    TEST_CLAUSE = TEST @Value(Areal_raster_ha) RANGE [@Evaluate(@Value(Areal_wkt_ha) * 0.9),@Evaluate(@Value(Areal_wkt_ha) * 1.1)]
    TEST_MODE = TEST
    PASSED -> AttributeCreator_5
    FAILED -> AttributeCreator_2
AttributeCreator_5
    ATTR_TABLE = SET_TO raster_status = OK
    -> FeatureMerger_3 [REQUESTOR]
AttributeCreator_2
    ATTR_TABLE = SET_TO raster_status = DELVIS_UTANFOR_EXTENT
    -> FeatureMerger_3 [REQUESTOR]
Note: Splitta punktmolnet för komponenten env i olika delar, utifrån valda koder
PointCloudSplitter
    OUTPUT_ATTR = CadasterENVkod
    SPLIT_BY_DISPLAY = env
    SPLIT_TYPE = Unique
    SPLIT -> PointCloudPropertyExtractor_8
    SPLIT -> PointCloudSplitter_Split
Note: Räkna punkter
PointCloudPropertyExtractor_8
    CALCULATE_EXTENTS_DISPLAY = No
    POINT_COMPONENTS = "env   "
    -> GeometryRemover
    -> PointCloudPropertyExtractor_8_Output
Note: Ta bort geometrin- snabba upp featuremerger
GeometryRemover
    -> AttributeCreator_4
AttributeCreator_4
    ATTR_TABLE = SET_TO id = 1
    -> AttributeFilter
Note: Filtrera ut koder
AttributeFilter
    ATTR_NAME = CadasterENVkod
    ATTR_VALUES = <Empty>,<Missing>,<Null>,<Unfiltered>,111,112,113,114,115,116,117,118,121,122,123,124,125,126,127,128,2,3,41,42,51,52,53,61,62,255
    111 -> ExpressionEvaluator_2
    111 -> ExpressionEvaluator_6
    112 -> ExpressionEvaluator_3
    112 -> ExpressionEvaluator_6
    113 -> ExpressionEvaluator_5
    113 -> ExpressionEvaluator_6
    114 -> ExpressionEvaluator_8
    114 -> ExpressionEvaluator_6
    115 -> ExpressionEvaluator_9
    115 -> ExpressionEvaluator_6
    116 -> ExpressionEvaluator_4
    116 -> ExpressionEvaluator_6
    117 -> ExpressionEvaluator_10
    117 -> ExpressionEvaluator_6
    118 -> ExpressionEvaluator_11
    118 -> ExpressionEvaluator_6
    121 -> ExpressionEvaluator_17
    122 -> ExpressionEvaluator_17
    123 -> ExpressionEvaluator_17
    124 -> ExpressionEvaluator_17
    125 -> ExpressionEvaluator_17
    126 -> ExpressionEvaluator_17
    127 -> ExpressionEvaluator_17
    128 -> ExpressionEvaluator_17
    2 -> ExpressionEvaluator_12
    3 -> ExpressionEvaluator_7
    41 -> ExpressionEvaluator_13
    42 -> ExpressionEvaluator_13
    51 -> ExpressionEvaluator_14
    52 -> ExpressionEvaluator_14
    53 -> ExpressionEvaluator_14
    61 -> ExpressionEvaluator_15
    62 -> ExpressionEvaluator_15
    255 -> ExpressionEvaluator_16
Note: Tallskog
ExpressionEvaluator_2
    ACTION = Create New Attribute
    EXPRESSION = @mult(0.01,@Value(_num_points))
    VAL_ATTR = tallskogHa
    -> Aggregator
Note: Granskog
ExpressionEvaluator_3
    ACTION = Create New Attribute
    EXPRESSION = @mult(0.01,@Value(_num_points))
    VAL_ATTR = granskogHa
    -> Aggregator
Note: Barrblandskog
ExpressionEvaluator_5
    ACTION = Create New Attribute
    EXPRESSION = @mult(0.01,@Value(_num_points))
    VAL_ATTR = barrblandskogHa
    -> Aggregator
Note: Lövblandad barrskog
ExpressionEvaluator_8
    ACTION = Create New Attribute
    EXPRESSION = @mult(0.01,@Value(_num_points))
    VAL_ATTR = lovblandadBarrskogHa
    -> Aggregator
Note: Triviallövskog
ExpressionEvaluator_9
    ACTION = Create New Attribute
    EXPRESSION = @mult(0.01,@Value(_num_points))
    VAL_ATTR = triviallovHa
    -> Aggregator
Note: Ädellöv
ExpressionEvaluator_4
    ACTION = Create New Attribute
    EXPRESSION = @mult(0.01,@Value(_num_points))
    VAL_ATTR = adellovHa
    -> Aggregator
Note: Triviallövskog med ädellöv
ExpressionEvaluator_10
    ACTION = Create New Attribute
    EXPRESSION = @mult(0.01,@Value(_num_points))
    VAL_ATTR = triviallovAdellovHa
    -> Aggregator
Note: Temporärt ej skog
ExpressionEvaluator_11
    ACTION = Create New Attribute
    EXPRESSION = @mult(0.01,@Value(_num_points))
    VAL_ATTR = temporartEjSkogHa
    -> Aggregator
Note: Skog ej på våtmark
ExpressionEvaluator_6
    ACTION = Create New Attribute
    EXPRESSION = @mult(0.01,@Value(_num_points))
    VAL_ATTR = skogHa
    -> Aggregator
    -> ExpressionEvaluator_6_Output
ExpressionEvaluator_6_Output: Inspector
Note: Skog på våtmark
ExpressionEvaluator_17
    ACTION = Create New Attribute
    EXPRESSION = @mult(0.01,@Value(_num_points))
    VAL_ATTR = skogVatmarkHa
    -> Aggregator
Note: Öppen Våtmark
ExpressionEvaluator_12
    ACTION = Create New Attribute
    EXPRESSION = @mult(0.01,@Value(_num_points))
    VAL_ATTR = oppenVatmarkHa
    -> Aggregator
Note: Åkermark
ExpressionEvaluator_7
    ACTION = Create New Attribute
    EXPRESSION = @mult(0.01,@Value(_num_points))
    VAL_ATTR = akermarkHa
    -> Aggregator
Note: Övrig Öppen Mark
ExpressionEvaluator_13
    ACTION = Create New Attribute
    EXPRESSION = @mult(0.01,@Value(_num_points))
    VAL_ATTR = ovrigOppenMarkHa
    -> Aggregator
Note: Exploaterad Mark
ExpressionEvaluator_14
    ACTION = Create New Attribute
    EXPRESSION = @mult(0.01,@Value(_num_points))
    VAL_ATTR = exploateradMarkHa
    -> Aggregator
Note: Vatten
ExpressionEvaluator_15
    ACTION = Create New Attribute
    EXPRESSION = @mult(0.01,@Value(_num_points))
    VAL_ATTR = vattenHa
    -> Aggregator
Note: Moln / Oklassat
ExpressionEvaluator_16
    ACTION = Create New Attribute
    EXPRESSION = @mult(0.01,@Value(_num_points))
    VAL_ATTR = molnOklassatHa
    -> Aggregator
Note: Aggregera till en rad
Aggregator
    ACCUM_ATTRS_NAME = Use Attributes From One Feature
    AGGREGATE_TYPE = Homogeneous Collection (If Possible)
    GROUP_BY = id
    MODE = Geometry - Assemble One Level
    SEP = ,
    SUM = molnOklassatHa skogVatmarkHa tallskogHa skogHa adellovHa akermarkHa temporartEjSkogHa ovrigOppenMarkHa triviallovHa barrblandskogHa triviallovAdellovHa granskogHa oppenVatmarkHa vattenHa exploateradMarkHa lovblandadBarrskogHa
    AGGREGATE -> AttributeKeeper_3
AttributeKeeper_3
    KEEP_ATTRS = molnOklassatHa,skogVatmarkHa,id,tallskogHa,skogHa,adellovHa,akermarkHa,temporartEjSkogHa,ovrigOppenMarkHa,triviallovHa,barrblandskogHa,triviallovAdellovHa,granskogHa,oppenVatmarkHa,vattenHa,exploateradMarkHa,lovblandadBarrskogHa
    -> FeatureMerger_3 [SUPPLIER]
FeatureMerger_3
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> AttributeRenamer_2
Note: Döp om attributen
AttributeRenamer_2
    ATTR_TABLE = RENAME_SET_DEFAULT Areal_wkt_ha > Area_ha
    -> AttributeRounder
Note: Avrunda. 3 decimaler
AttributeRounder
    PLACES = 3
    ROUND_TYPE = Nearest
    SRC_ATTRS = molnOklassatHa skogVatmarkHa tallskogHa skogHa adellovHa akermarkHa Area_ha temporartEjSkogHa ovrigOppenMarkHa triviallovHa barrblandskogHa triviallovAdellovHa granskogHa oppenVatmarkHa vattenHa exploateradMarkHa lovblandadBarrskogHa
    -> AttributeRounder_3
Note: Avrunda area_ha. Inga decimaler
AttributeRounder_3
    PLACES = 1
    ROUND_TYPE = Nearest
    SRC_ATTRS = Area_ha
    -> AttributeCreator_3
PointCloudPropertyExtractor_8_Output: Inspector
PointCloudSplitter_Split: Inspector
